Module-sequence-test DEFINITIONS AUTOMATIC TAGS ::= BEGIN

  Sleep-time-t ::= SEQUENCE {
    begin Time-t,
    end Time-t
  }

  Time-t ::= SEQUENCE {
    hour INTEGER(0..23),     -- [h] 24 h format
    minute INTEGER(0..59)     -- [min] 1 h == 60 min
  }

END
