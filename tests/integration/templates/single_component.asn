Module-single-component-test DEFINITIONS AUTOMATIC TAGS ::= BEGIN

  Sandbox-ping ::= SEQUENCE {
    primary-header Ccsds-primary-header
      (WITH COMPONENTS {
        packet-version-number (0)
      }),
    secondary-header INTEGER(1..3)
  }

  Ccsds-primary-header ::= SEQUENCE {
    packet-version-number INTEGER(0..7),     -- 3bit, 0b000 to 0b111
    packet-identification INTEGER(-1..1),
    packet-sequence-control INTEGER(2..3),
    packet-data-length INTEGER(3..4)
  }

END
