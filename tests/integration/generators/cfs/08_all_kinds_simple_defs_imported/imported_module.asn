Module-imported-module DEFINITIONS AUTOMATIC TAGS ::= BEGIN

  Percent ::= REAL(0.0 .. 100.00)
  Float ::= REAL(-340000000000000000000000000000000000000.00 .. 340000000000000000000000000000000000000.00)
  Double ::= REAL(-179769313486231570000000000000000000000000000000000000000000000000000000000000000000000000000000000000000000000000000000000000000000000000000000000000000000000000000000000000000000000000000000000000000000000000000000000000000000000000000000000000000000000000000000000000000000000000000000000000000000000000000.0 .. 179769313486231570000000000000000000000000000000000000000000000000000000000000000000000000000000000000000000000000000000000000000000000000000000000000000000000000000000000000000000000000000000000000000000000000000000000000000000000000000000000000000000000000000000000000000000000000000000000000000000000000000.0)

  Uint3 ::= INTEGER(0..7)
  Uint16-t ::= INTEGER(0..65535)

END
