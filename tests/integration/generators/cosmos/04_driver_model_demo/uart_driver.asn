Module-uart-driver DEFINITIONS AUTOMATIC TAGS ::= BEGIN

  IMPORTS Cfe-tlm-header FROM Module-cfe-headers
          Real-range FROM Module-simple-types;



  Uart-driver-uart0-read-tlm ::= SEQUENCE { -- UART_DRIVER_UART_0_READ_MID uart_driver_ReadTlm_t (0x08D0)
    header Cfe-tlm-header (WITH COMPONENTS {
      primary (WITH COMPONENTS {
        packet-version-number (0),
        packet-identification (WITH COMPONENTS {
          packet-type-is-cmd (FALSE),
          sec-hdr-flag-is-present (TRUE),
          application-process-identifier (208)
        })
      })
    }),
    payload Payload-uart-driver
  }

  Uart-driver-uart1-read-tlm ::= SEQUENCE { -- UART_DRIVER_UART_1_READ_MID uart_driver_ReadTlm_t (0x08D1)
    header Cfe-tlm-header (WITH COMPONENTS {
      primary (WITH COMPONENTS {
        packet-version-number (0),
        packet-identification (WITH COMPONENTS {
          packet-type-is-cmd (FALSE),
          sec-hdr-flag-is-present (TRUE),
          application-process-identifier (209)
        })
      })
    }),
    payload Payload-uart-driver
  }



  Payload-uart-driver ::= SEQUENCE {
    raw Real-range -- [m] TODO String
  }

END
