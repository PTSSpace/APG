Module-sandbox-hk-pc DEFINITIONS AUTOMATIC TAGS ::= BEGIN

  IMPORTS Ccsds-primary-header, Secondary-header FROM Module-tmtc-header
          Uint64-t FROM Module-simple-types;

  Percent-range ::= REAL(0.00 .. 100.00)
  Load-range ::= REAL(0.00 .. 30.00)

  Sandbox-hk-pc ::= SEQUENCE { -- (0x0899) SANDBOX PC housekeeping telemetry
    primary-header Ccsds-primary-header
      (WITH COMPONENTS {
        packet-version-number (0),
        packet-identification (WITH COMPONENTS {
          packet-type-is-cmd (FALSE),
          sec-hdr-flag-is-present (TRUE),
          application-process-identifier (153)
        })
      }),
    secondary-header Secondary-header,
    payload Payload-sandbox-hk-pc
  }

  Payload-sandbox-hk-pc ::= SEQUENCE {
    cpu Percent-range, -- [%] CPU usage
    load1 Load-range, -- load from 1 minute average
    load5 Load-range, -- load from 5 minutes average
    load15 Load-range, -- load from 15 minutes average
    total-ram Uint64-t, -- [byte] total RAM
    free-ram Uint64-t, -- [byte] free RAM
    free-swap Uint64-t -- [byte] free SWAP
  }

END
