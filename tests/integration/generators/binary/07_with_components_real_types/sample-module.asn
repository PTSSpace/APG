Module-sample-module DEFINITIONS AUTOMATIC TAGS ::= BEGIN

  Float ::= REAL(-340000000000000000000000000000000000000.00 .. 340000000000000000000000000000000000000.00)
  Double ::= REAL(-179769313486231570000000000000000000000000000000000000000000000000000000000000000000000000000000000000000000000000000000000000000000000000000000000000000000000000000000000000000000000000000000000000000000000000000000000000000000000000000000000000000000000000000000000000000000000000000000000000000000000000000.0 .. 179769313486231570000000000000000000000000000000000000000000000000000000000000000000000000000000000000000000000000000000000000000000000000000000000000000000000000000000000000000000000000000000000000000000000000000000000000000000000000000000000000000000000000000000000000000000000000000000000000000000000000000.0)

  Sample-packet ::= SEQUENCE {
    sample-packet-with-component With-component-packet (WITH COMPONENTS { -- <fd
      with-component-packet-number-1 (170141183460469231731687303715884105728.0), -- 2^127
      with-component-packet-number-2 (390000000000000000000000000000000000000.0)
    })
  }

  With-component-packet ::= SEQUENCE {
    with-component-packet-number-1 Float,
    with-component-packet-number-2 Double
  }

END
