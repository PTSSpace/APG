Module-sample-module DEFINITIONS AUTOMATIC TAGS ::= BEGIN

  Sample-packet ::= SEQUENCE {
    sample-packet-with-component With-component-packet (WITH COMPONENTS { -- >IQBH
      with-component-packet-number-1 (23),
      with-component-packet-number-2 (42),
      with-component-packet-inner-with-component (WITH COMPONENTS {
        inner-with-component-packet-number-1 (1),
        inner-with-component-packet-number-2 (9)
      })
    })
  }

  With-component-packet ::= SEQUENCE {
    with-component-packet-number-1 INTEGER(0..4294967295), -- 32 bit
    with-component-packet-number-2 INTEGER(0..18446744073709551615), -- 64 bit
    with-component-packet-inner-with-component Inner-with-component-packet
  }

  Inner-with-component-packet ::= SEQUENCE {
    inner-with-component-packet-number-1 INTEGER(0..255), -- 8 bit
    inner-with-component-packet-number-2 INTEGER(0..65535) -- 16 bit
  }

END
